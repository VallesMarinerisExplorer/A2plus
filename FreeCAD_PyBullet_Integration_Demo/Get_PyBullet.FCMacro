# If you do not already have pybullet installed in FreeCAD run this FreeCAD Macro and it will install it for you
# It should work if you have python 3.8 - 3.11 for FreeCAD

import FreeCAD
FreeCADPath = FreeCAD.__path__[1]
FreeCADPathbin = FreeCADPath.replace("lib","bin")
FreeCADPath = FreeCADPathbin + "\\Scripts\\pip"
FreeCADSitepackages = FreeCADPathbin + "\\Lib\\site-packages"

try:
    import pybullet as p
except:
    import subprocess
    print("Installing PyBullet\n"
          "This may take a minute...")
    try:
        import requests
    except subprocess.CalledProcessError as e:
        subprocess.check_call([FreeCADPath, "install", "requests"])
    try:
	    import zipfile
    except subprocess.CalledProcessError as e:
         subprocess.check_call([FreeCADPath, "install", "zipfile"])
    import requests
	# Download the PyBullet from the expedited install repo
    url = "https://github.com/VallesMarinerisExplorer/PyBullet_Extensions/archive/refs/heads/main.zip"
    response = requests.get(url)
    response.raise_for_status()  # Raise an exception for HTTP errors

    filename = url.split("/")[-1]  # Extract filename from URL

    with open(filename, 'wb') as file:
        file.write(response.content)
    
    filename = FreeCADPathbin + "\\" + filename
    print(filename)
    with zipfile.ZipFile(filename, 'r') as zip_ref:
        zip_ref.extractall(FreeCADPathbin)

    with zipfile.ZipFile(r'\\?\\' + FreeCADPathbin + "\\PyBullet_Extensions-main\\pybullet-download.zip", 'r') as zip_ref:
        zip_ref.extractall(r'\\?\\' + FreeCADPathbin + "\\PyBullet_Extensions-main")
    
    import shutil

    # Define the source and destination directories
    source_dir = r'\\?\\' + FreeCADPathbin + "\\PyBullet_Extensions-main\\pybullet-download"

    # Get the subfolders of the source parent directory
    subfolders = [f for f in os.listdir(source_dir) if os.path.isdir(os.path.join(source_dir, f))]

    # Copy each subfolder to the destination directory
    for subfolder in subfolders:
        source_subfolder = os.path.join(source_dir, subfolder)
        try:
            shutil.copytree(source_subfolder, os.path.join(FreeCADSitepackages, subfolder))
        except shutil.Error as e:
            print(f"Error copying {subfolder}: {e}")
        except OSError as e:
            print(f"OS error encountered for {subfolder}: {e}")

    src_files = os.listdir(source_dir)
    for file_name in src_files:
        full_file_name = os.path.join(source_dir, file_name)
        if os.path.isfile(full_file_name):
            shutil.copy(full_file_name, FreeCADSitepackages)

    pybversion = str(sys.version_info.major) + str(sys.version_info.minor)
    pybulletfile = FreeCADPathbin + "\\PyBullet_Extensions-main\\pybullet.cp" +pybversion + "-win_amd64.pyd"
    shutil.copy(pybulletfile, FreeCADSitepackages + "\\pybullet.cp" + pybversion + "-win_amd64.pyd")

    import pybullet as p
