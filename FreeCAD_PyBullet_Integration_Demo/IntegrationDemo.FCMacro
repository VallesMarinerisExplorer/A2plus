import FreeCAD

# If you do not already have pybullet installed in FreeCAD run this FreeCAD Macro and it will install it for you
# It should work if you have python 3.8 - 3.11 for FreeCAD

import FreeCAD
FreeCADPath = FreeCAD.__path__[1]
FreeCADPathbin = FreeCADPath.replace("lib","bin")
FreeCADPath = FreeCADPathbin + "\\Scripts\\pip"
FreeCADSitepackages = FreeCADPathbin + "\\Lib\\site-packages"

# Try to import pybullet, if cannot then download and install. This is done instead of pip installing b/c in order to do
# that you need to have Microsoft C++ build tools to pip install I think. Probably worth looking into how to eliminate 
# this build dependency for most users/creating a new pip/pypi package w/out need for C++ build tools
try:
    import pybullet as p
except:
    import subprocess
    print("Installing PyBullet\n"
          "This may take a minute...")
    try:
        import requests
    except subprocess.CalledProcessError as e:
        subprocess.check_call([FreeCADPath, "install", "requests"])
    try:
	    import zipfile
    except subprocess.CalledProcessError as e:
         subprocess.check_call([FreeCADPath, "install", "zipfile"])
    import requests
	# Download the PyBullet from the expedited install repo
    url = "https://github.com/VallesMarinerisExplorer/PyBullet_Extensions/archive/refs/heads/main.zip"
    response = requests.get(url)
    response.raise_for_status()  # Raise an exception for HTTP errors

    filename = url.split("/")[-1]  # Extract filename from URL

    with open(filename, 'wb') as file:
        file.write(response.content)
    
    filename = FreeCADPathbin + "\\" + filename
    print(filename)
    with zipfile.ZipFile(filename, 'r') as zip_ref:
        zip_ref.extractall(FreeCADPathbin)

    with zipfile.ZipFile(r'\\?\\' + FreeCADPathbin + "\\PyBullet_Extensions-main\\pybullet-download.zip", 'r') as zip_ref:
        zip_ref.extractall(r'\\?\\' + FreeCADPathbin + "\\PyBullet_Extensions-main")
    
    import shutil

    # Define the source and destination directories
    source_dir = r'\\?\\' + FreeCADPathbin + "\\PyBullet_Extensions-main\\pybullet-download"

    # Get the subfolders of the source parent directory
    subfolders = [f for f in os.listdir(source_dir) if os.path.isdir(os.path.join(source_dir, f))]

    # Copy each subfolder to the destination directory
    for subfolder in subfolders:
        source_subfolder = os.path.join(source_dir, subfolder)
        try:
            shutil.copytree(source_subfolder, os.path.join(FreeCADSitepackages, subfolder))
        except shutil.Error as e:
            print(f"Error copying {subfolder}: {e}")
        except OSError as e:
            print(f"OS error encountered for {subfolder}: {e}")

    src_files = os.listdir(source_dir)
    for file_name in src_files:
        full_file_name = os.path.join(source_dir, file_name)
        if os.path.isfile(full_file_name):
            shutil.copy(full_file_name, FreeCADSitepackages)

    pybversion = str(sys.version_info.major) + str(sys.version_info.minor)
    pybulletfile = FreeCADPathbin + "\\PyBullet_Extensions-main\\pybullet.cp" +pybversion + "-win_amd64.pyd"
    shutil.copy(pybulletfile, FreeCADSitepackages + "\\pybullet.cp" + pybversion + "-win_amd64.pyd")

    import pybullet as p

import time
import os
# Get the FreeCAD object
obj = FreeCAD.ActiveDocument.getObject("Body")

# Get the current position and orientation of the FreeCAD object
position = obj.Placement.Base
rotation = obj.Placement.Rotation

# Convert FreeCAD rotation to pybullet quaternion
# FreeCAD uses (w, x, y, z) quaternion format
# pybullet uses (x, y, z, w) quaternion format
quaternion = [rotation.Q[0], rotation.Q[1], rotation.Q[2], rotation.Q[3]]

# Initialize pybullet
p.connect(p.DIRECT)  # Use p.GUI for a graphical interface

# Create a pybullet world
p.resetSimulation()

# Load the FreeCAD object's position and orientation into pybullet
# This assumes the .fcstd and .urdf files are in the same directory
urdfpath = FreeCAD.ActiveDocument.getFileName().replace(".FCStd",".urdf")
box_id = p.loadURDF(urdfpath, basePosition=position, baseOrientation=quaternion)

# Set initial angular velocity
initial_angular_velocity = [3, -10, 1]  # Replace with your desired angular velocity [x, y, z]
p.resetBaseVelocity(box_id, linearVelocity=[0, 0, 0], angularVelocity=initial_angular_velocity)


i = 0
while i <= 300:

    new_position, new_quaternion = p.getBasePositionAndOrientation(box_id)
    
    rot = App.Rotation(new_quaternion[0],new_quaternion[1],new_quaternion[2],new_quaternion[3])    
    obj.Placement = FreeCAD.Placement(obj.Placement.Base, rot)

    FreeCAD.ActiveDocument.recompute()
    Gui.updateGui()
    # Wait until the document has been recomputed
    while "Recompute" in obj.State:
        pass
    p.stepSimulation()

    i += 1
